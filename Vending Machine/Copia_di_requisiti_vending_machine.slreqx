# Copia_di_requisiti_vending_machine

## Copia di requisiti_vending_machine!Sheet1: References to Copia di requisiti_vending_machine.xlsx (Sheet1) (Container)
Read-only references to Microsoft Excel document.

### R1: Tipologia Bevande (Functional)
la macchina eroga  bevande: caffe, the e cioccolata

### R2: Tipologia Pagamento (Functional)
la macchina accetta pagamenti sia in contanti che con la pennetta.

### R3: Opzioni Prodotti (Functional)
le opzioni zuccherato niente medio molto (012) Se 0 no bacchetta. 3 size piccolo - medio - grande  . bisogna prenotare tutte le opzioni

### R4: Costo Prodotti (Functional)
tutte le bevande con le diverse opzioni costano uguale

### R5: Tipologia di Inserimento (Functional)
Mediante Tastierino con un display che mostra il prezzo

### R6: Gestione Inattività (Functional)
Nella fase di attesa di inserimento credito, si aspetta  per un timeout di 10 secondi, in caso negativo si torna nel caso iniziale

### R7: Gestione Contanti (Functional)
nel caso in cui si utilizza contanti la macchina conta i contati inseriti fino ad arrivare all'importo richiesto.

### R8: Gestione Monete False (Functional)
se la moneta inserita non viene riconosciuta la macchina restituisce la moneta

### R9: Gestione Chiavetta (Functional)
nel caso in cui si usi la  la pennetta controlla che questa abbia abbastanza credito in caso contrario segnala la dovuta ricarica e aspetta che la pennetta sia ricaricata

### R10: Credito Insufficiente (Functional)
nel caso in cui il credito non sia sufficiente si aspetta  per un timeout di 10 secondi, in caso negativo si torna nel caso iniziale regettando le monente inserite se presenti

### R11: Gestione Resto (Functional)
Se inserita la chiavetta si sottrae il credito alla pennetta altrimenti da il resto in monete

### R12: Erogazione Prodotto (Functional)
La macchina eroga il prodotto se ogni opzione bevanda è selezionata e il credito è sufficiente
