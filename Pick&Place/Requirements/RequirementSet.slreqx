# RequirementSet

## Pick_place!Sheet1: References to Pick_place.xlsx (Sheet1) (Container)
Imported from Microsoft Excel

### 1: Scatola 1: stato 0,1,2 = N pezzi (Functional)

### 2: Scatola 2: stato 0,1,2,3,4 = N pezzi (Functional)

### 3: Scatola 3: stato 0,1,2,3,4,5,6 = N pezzi (Functional)

### 4: Lo stato iniziale di ciascuna scatola è quello della massima capienza pe rle scatole 1 e 2 e di vuoto per la scaola 3 (Functional)

### 5: Ciascuna scatola ha un campo di availability che viene settato da un bottone esterno (scatola presente o meno) Status availability scatola: on/off pulsante (Functional)

### 6: Il prelievo ed il deposito da una scatola ordinata (Functional)

### 7: Mostra status workspace (IsReady = 0,1) pezzo 3 assemblato o meno (Functional)

### 8: Check che sia disponibile il pezzo1, pezzo2 e che lo spoazio di lavoro sia libero (IsFree) (Functional)

### 9: La presenza o meno di un elemento nello spazio di laoro è fornita dall'esterno con un bottone (Functional)

### 10: L'utensile o l'operatore verificano la presenza dei due pezzi e può iniziare l'assemblaggio (AssemblyStatus true) (Functional)

### 11: Utensile: Availability + IsReady = AssemblyStatus (Functional)

### 12: Operatore: Availability + IsReady = AssemblyStatus (Functional)

### 13: L'utensile o l'operatore eseguono l'assemblaggio. Se Assembly Status di operatore OR di utensile sono posti a true, l'assemblaggio può cominciare e termina dopo un certo ritardo (Functional)

### 14: La macchina verifica che il pezzo sia montato (IsReady) (Functional)

### 15: Verifica Scatola 1 Availability (Functional)

### 16: Verifica Scatola 1 Capienza != 0 (Functional)

### 17: Preleva Scatola 1 --> Pezzo1 e decrementa la capienza ( cambia di stato la capienza) (Functional)

### 18: Verifica Scatola 2 Availability (Functional)

### 19: Verifica Scatola 2 != 0 (Functional)

### 20: Preleva Scatola 2 --> Pezzo2 decrementa la capienza ( cambia di stato la capienza) (Functional)

### 21: Verifica Scatola 3 Availability (Functional)

### 22: Verifica Scatola 3 Capienza != 6 (Functional)

### 23: Verifica della presenza del pezzo 3 (Functional)

### 24: Verifica della capienza delle tre scatole (Functional)

### 25: Sostituzione scatola piena (se scatola 3) o sosituzione delle scatole 1 e 2 se vuote (Functional)

### 26: Deposita Scatola 3 --> Pezzo3 (Functional)

### 27: 2 led scatola 1 0-1 per ogni posizione (Functional)

### 28: 4 led scatola 2 0-1 per ogni posizione (Functional)

### 29: 6 led scatola 3 0-1 per ogni posizione (Functional)

### 30: 1 tasto operatore/utensile (Functional)
